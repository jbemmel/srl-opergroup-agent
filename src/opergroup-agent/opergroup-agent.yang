module opergroup-agent {

    yang-version "1";

    // namespace
    namespace "urn:srl_test/opergroup-agent";

    prefix "opergroup_agent";

    revision "2021-06-28" {
        description "Initial revision";
        reference "TBD";
    }

    grouping opergroup-agent-top {
        description "Top level grouping for OperGroup agent app";

        container opergroup-agent {
            presence "presence container";
            description "Top level enclosing container for opergroup app
                         config and operational state data";


            list oper-group {
              key name;
              ordered-by user;

              leaf name {
                type string;
                description "Unique name for this fate-sharing operational group";
              }
              leaf description {
                type string;
                description "Description for this group, not processed";
              }
              leaf monitor {
                type string;
                description "gNMI path to monitor for changes";
              }
              leaf current-states {
                type string;
                description "Current value of monitored operational gNMI state(s)";
                config false;
              }
              leaf group-state {
                type string;
                description "Resulting group state";
                config false;
              }
              leaf based-on {
                type string;
                description "Condition that resulted in group state";
                config false;
              }
              leaf last-change {
                type string;
                description "Timestamp of last state change";
                config false;
              }
              leaf target-count {
                type uint16;
                description "Number of affected objects (e.g. links)";
                config false;
              }
              leaf down {
                type uint16;
                description "Number of monitored objects that are not up";
                config false;
              }
              leaf targets {  // tried leaf-list, hard to populate
                type string;
                description "gNMI target paths affected";
                config false;
              }
              leaf target-path {
                type string;
                description "gNMI path expression to apply the same changes";
              }
              leaf mapping {
                type string;
                description "List of input=output mapping values to apply";
                default "up=enable,down=disable";
              }
              leaf expression {
                type string;
                description "Optional list of expression=<target state> values, for example int(_)<2:disable,True:enable";
              }
              leaf default {
                type string;
                description "Default state to use if none of the expressions match, default 'enable'";
                default "enable";
              }
              leaf threshold {
                description "Trigger condition; default 'any' links down";
                type enumeration {
                  enum any;
                  enum all;
                  enum "1";
                  enum "2";
                  enum "3";
                  enum "4";
                  enum "50%";
                }
                default any;
              }
            }
        }
    }

    // data definition statements
    uses opergroup-agent-top;
}
