module opergroup-agent {

    yang-version "1";

    // namespace
    namespace "urn:srl_test/opergroup-agent";

    prefix "opergroup_agent";

    revision "2021-06-28" {
        description "Initial revision";
        reference "TBD";
    }

    grouping opergroup-agent-top {
        description "Top level grouping for OperGroup agent app";

        container opergroup-agent {
            presence "presence container";
            description "Top level enclosing container for opergroup app
                         config and operational state data";


            list oper-group {
              key name;

              leaf name {
                type string;
                description "Unique name for this fate-sharing operational group";
              }
              leaf monitor {
                type string;
                description "gNMI path to monitor for changes";
              }
              leaf current-state {
                type string;
                description "Current value of monitored operational gNMI state";
                config false;
              }
              leaf last-change {
                type string;
                description "Timestamp of last state change";
                config false;
              }
              leaf target-count {
                type uint16;
                description "Number of affected objects (e.g. links)";
                config false;
              }
              leaf targets {  // tried leaf-list, hard to populate
                type string;
                description "gNMI target paths affected";
                config false;
              }
              leaf group {
                type string;
                description "gNMI path expression to apply the same changes";
              }
            }
        }
    }

    // data definition statements
    uses opergroup-agent-top;
}
